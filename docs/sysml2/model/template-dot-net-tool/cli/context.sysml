package TemplateDotNetTool {
    part def Context {
        doc /* Command-line argument parser and I/O owner for one tool invocation. */

        comment sourceRef /* Source: src/DemaConsulting.TemplateDotNetTool/Cli/Context.cs */
        comment testRef /* Test: test/DemaConsulting.TemplateDotNetTool.Tests/Cli/ContextTests.cs */
        comment designRef /* Design: docs/design/template-dot-net-tool/cli/context.md */
        comment verificationRef /* Verification: docs/verification/template-dot-net-tool/cli/context.md */
        comment reqRef /* Requirements: docs/reqstream/template-dot-net-tool/cli/context.yaml */
    }
}
