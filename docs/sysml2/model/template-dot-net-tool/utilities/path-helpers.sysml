package TemplateDotNetTool {
    part def PathHelpers {
        doc /* Safe path-combination utility guarding against path-traversal. */

        comment sourceRef /* Source: src/DemaConsulting.TemplateDotNetTool/Utilities/PathHelpers.cs */
        comment testRef /* Test: test/DemaConsulting.TemplateDotNetTool.Tests/Utilities/PathHelpersTests.cs */
        comment designRef /* Design: docs/design/template-dot-net-tool/utilities/path-helpers.md */
        comment verificationRef /* Verification: docs/verification/template-dot-net-tool/utilities/path-helpers.md */
        comment reqRef /* Requirements: docs/reqstream/template-dot-net-tool/utilities/path-helpers.yaml */
    }
}
