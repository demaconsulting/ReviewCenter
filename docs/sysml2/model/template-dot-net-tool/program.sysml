package TemplateDotNetTool {
    part def Program {
        doc /* Entry point and execution orchestrator. */

        comment sourceRef /* Source: src/DemaConsulting.TemplateDotNetTool/Program.cs */
        comment testRef /* Test: test/DemaConsulting.TemplateDotNetTool.Tests/ProgramTests.cs */
        comment designRef /* Design: docs/design/template-dot-net-tool/program.md */
        comment verificationRef /* Verification: docs/verification/template-dot-net-tool/program.md */
        comment reqRef /* Requirements: docs/reqstream/template-dot-net-tool/program.yaml */
    }
}
