package TemplateDotNetTool {
    part def Validation {
        doc /* Orchestrates the self-validation test suite and reports pass/fail results. */

        comment sourceRef /* Source: src/DemaConsulting.TemplateDotNetTool/SelfTest/Validation.cs */
        comment testRef /* Test: test/DemaConsulting.TemplateDotNetTool.Tests/SelfTest/ValidationTests.cs */
        comment designRef /* Design: docs/design/template-dot-net-tool/self-test/validation.md */
        comment verificationRef /* Verification: docs/verification/template-dot-net-tool/self-test/validation.md */
        comment reqRef /* Requirements: docs/reqstream/template-dot-net-tool/self-test/validation.yaml */
    }
}
