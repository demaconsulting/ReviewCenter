package ReviewCenterPuppet {
    part def DaemonLauncher {
        doc /* Starts the session daemon as a detached background process that outlives the calling command. */

        comment sourceRef /* Source: tools/puppet/DaemonLauncher.cs */
        comment testRef /* Test: test/DemaConsulting.ReviewCenter.Puppet.Tests/DaemonLauncherTests.cs */
        comment designRef /* Design: docs/design/review-center-puppet/daemon-launcher.md */
        comment verificationRef /* Verification: docs/verification/review-center-puppet/daemon-launcher.md */
        comment reqRef /* Requirements: docs/reqstream/review-center-puppet/daemon-launcher.yaml */
    }
}
