package ReviewCenterPuppet {
    part def StepRunner {
        doc /* Reads and validates a steps file and runs its steps against an abstract browser page. */

        comment sourceRef /* Source: tools/puppet/StepFile.cs, tools/puppet/StepRunner.cs */
        comment testRef /* Test: test/DemaConsulting.ReviewCenter.Puppet.Tests/StepRunnerTests.cs */
        comment designRef /* Design: docs/design/review-center-puppet/step-runner.md */
        comment verificationRef /* Verification: docs/verification/review-center-puppet/step-runner.md */
        comment reqRef /* Requirements: docs/reqstream/review-center-puppet/step-runner.yaml */
    }
}
