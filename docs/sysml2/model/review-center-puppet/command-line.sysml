package ReviewCenterPuppet {
    part def CommandLine {
        doc /* Strict parser for the Puppet verb, positional arguments, and global options. */

        comment sourceRef /* Source: tools/puppet/CommandLine.cs */
        comment testRef /* Test: test/DemaConsulting.ReviewCenter.Puppet.Tests/CommandLineTests.cs */
        comment designRef /* Design: docs/design/review-center-puppet/command-line.md */
        comment verificationRef /* Verification: docs/verification/review-center-puppet/command-line.md */
        comment reqRef /* Requirements: docs/reqstream/review-center-puppet/command-line.yaml */
    }
}
