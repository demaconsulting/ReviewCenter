package ReviewCenterPuppet {
    part def CommandExecutor {
        doc /* Executes browser commands against an abstract page and turns each outcome into a control response. */

        comment sourceRef /* Source: tools/puppet/CommandExecutor.cs */
        comment testRef /* Test: test/DemaConsulting.ReviewCenter.Puppet.Tests/CommandExecutorTests.cs */
        comment designRef /* Design: docs/design/review-center-puppet/command-executor.md */
        comment verificationRef /* Verification: docs/verification/review-center-puppet/command-executor.md */
        comment reqRef /* Requirements: docs/reqstream/review-center-puppet/command-executor.yaml */
    }
}
