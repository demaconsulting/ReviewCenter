package ReviewCenter {
    private import SoftwareItemMetadata::*;

    part def KeyRingProtection {
        doc /* Decides how the Data Protection key ring is protected at rest and owns the `DataProtection` settings: `Auto` (the default) chooses the certificate when `DataProtection:CertificatePath` is set, otherwise Windows DPAPI on Windows and the permissions of the key folder (0700, key files 0600, also for files created while the server runs; an owner-only access rule on Windows with `PermissionsOnly`) with a warning at every start elsewhere; `Dpapi` (current user or local machine, Windows only), `Certificate` (an RSA certificate with a private key from a PFX, PKCS#12, or PEM file, with the password resolved by SecretSource and previous certificates that can still decrypt the ring), and `PermissionsOnly` can be chosen explicitly, and `RequireEncryptedKeys` refuses a ring that is not encrypted, and `AllowNewKeyRing` (off by default) accepts a new ring although the database holds protected secrets. It describes a ring without touching it (the number of key files and how many are not encrypted). It wires the encryption into the Data Protection builder and checks the ring before a key can be created, so that a wrong certificate stops the start instead of silently creating a new key. A wrong setting stops the start with a message that names the setting and never holds the password. */

        metadata info : SoftwareInfo {
            sourceFiles = ("src/DemaConsulting.ReviewCenter/Hosting/KeyRingProtection.cs", "src/DemaConsulting.ReviewCenter/Hosting/KeyRingProtectionMode.cs");
            testFiles = ("test/DemaConsulting.ReviewCenter.Tests/Hosting/KeyRingProtectionTests.cs");
            designFiles = ("docs/design/review-center/hosting/key-ring-protection.md");
            verificationFiles = ("docs/verification/review-center/hosting/key-ring-protection.md");
            requirementFiles = ("docs/reqstream/review-center/hosting/key-ring-protection.yaml");
        }
    }
}
