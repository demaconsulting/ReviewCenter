package ReviewCenter {
    private import SoftwareItemMetadata::*;

    part def ServerHost {
        doc /* Composition root that builds and runs the ASP.NET Core web application behind the serve verb, including the database, the domain services (including the signing service, the repository service, and the project access rules, which are one shared instance), the git source with validated settings (`Git:TimeoutSeconds` 1 to 3600), the persisted Data Protection key ring (its protection and checks are delegated to KeyRingProtection, and the refusal of a lost ring, an empty key folder next to a database with protected secrets, to SecretScan; the command-line verbs do neither), the signed attestation (its settings, key provider, which is given the Data Protection provider of the server so that the self-signed key is protected by the key ring, services, and endpoint, with a start-up check of the signing key), the authentication pipeline, the start-up validation of the `Identity:Oidc` settings (a failure names the setting, never a value) with the OpenID Connect sign-in registered only when enabled and `/signin-oidc` reserved, the start-up validation of the `Identity:Totp` settings with the services of the second factor registered and the endpoint of its second step mapped only when enabled, the single shared store of the sign-in proofs, the start-up validation of the `Notifications` settings (off by default and not checked while off; a failure names the setting, never a secret; an inline password is logged as a warning, and a database without the notification tables stops the start only while notifications are on) with the registration of the sender, the notification store, and the notification address service (the background notification worker is registered by the web host only, and only while notifications are enabled with a transport), the personal access token service, the API routes under /api, and the OpenAPI document. With `ServerHostOptions.IsolatedSettings` it is built from an empty builder that reads nothing but the given settings (used by the self-validation host check). */

        metadata info : SoftwareInfo {
            sourceFiles = ("src/DemaConsulting.ReviewCenter/Hosting/ServerHost.cs");
            testFiles = ("test/DemaConsulting.ReviewCenter.Tests/Hosting/ServerHostTests.cs", "test/DemaConsulting.ReviewCenter.Tests/Hosting/ServerHostNotificationWorkerTests.cs");
            designFiles = ("docs/design/review-center/hosting/server-host.md");
            verificationFiles = ("docs/verification/review-center/hosting/server-host.md");
            requirementFiles = ("docs/reqstream/review-center/hosting/server-host.yaml");
        }
    }
}
