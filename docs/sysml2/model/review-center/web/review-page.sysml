package ReviewCenter {
    private import SoftwareItemMetadata::*;

    part def ReviewPage {
        doc /* Page that shows one review with the reader's work first: a next-step line, a compact summary strip (checklist progress with a link to the checklist, the reviewer state, and the open and resolved thread counts), the files, a thread index across all files (filtered by state; choosing a row selects the file and scrolls to and highlights the anchor), and the numbered lines of a selected file with its comment threads, which readers can start, answer, resolve, and reopen (resolved threads collapse to one line). Every file, line and thread has a stable address (/files/{path} with an optional line and side, and /threads/{id}) that opens the page at that place with the line or thread highlighted; choosing a file or thread replaces the address of the browser by its link, every thread has a button-styled Link and a Copy link button that copies the absolute address, and an address that names nothing gives a message with a link back to the file list. It also shows each file's change kind for a review from a repository, the source (repository, review-set, commits, selection), and for a file of a review with a baseline a Diff view (the default: the baseline and the head side by side with their own line numbers, unchanged lines collapsed, comments on a line of either version shown under its row, and the control to comment on a line shown when the row is hovered or focused; an added file is all added lines and a deleted file all removed lines), the Head version (with comments; not for a deleted file) and a read-only Baseline version (not for an added file). The review's identifier, state, fingerprint, and file hashes are in a collapsed Details section after the reviewers and signing card. It also shows the approval (Approved or In review) with the reviewer slots, where any signed-in user who may see the project manages the slots, choosing among the members of the project and marking a reviewer who is no longer a member ("No longer a project member", who cannot sign), a reviewer signs a slot after entering the password again (with a fresh code of the authenticator app beside it when the reviewer has a second factor; a reviewer who signed in with an OpenID Connect provider instead confirms the identity at the provider with a button, and then signs), and the blockers and the record digest are shown. An approved review is shown as locked (a Locked badge and a banner, every control that changes the review disabled) and an administrator of the project or a system administrator can reopen it with a reason, after which the reopenings are listed; a new comment, a reply, or a resolve or reopen of a thread that would change the report, so that a current signature has to be given again, first shows a warning that names the signers and goes on only when the reader confirms; while the project requires independent reviewers the author of the review is not offered as a reviewer and is told so; while the project does not let the person who reopened a review sign it again, that person sees a notice instead of the sign form, and a reopen that would leave a slot without anyone who may sign shows the refusal of Core. For a concluded review (approved or rejected) it offers the download of the signed attestation, with a note on the kind of the signing key, or the reason why the key cannot be used. A review that follows another shows a link to it with the number of carried answers and threads, a review that is followed lists its follow-ups, and a carried thread is marked with the review it came from. The comments of others that the viewer has not seen yet carry a New marker in the summary, the thread index, and the thread, and the page stores that the viewer has seen the comments once it is live. Every thread is a Question (a neutral speech-bubble icon and the word Question) or a Finding (an amber flag, the word Finding and an In report badge), drawn by `ThreadKindBadge` and never by color alone; `ThreadComposer` starts a thread as a Question or a Finding and has the Add to report box of a reply; `ThreadCard` shows a thread with chat bubbles or In report marks and the buttons that the capabilities of Core allow (make a Finding, make a Question, add to or remove from the report, resolve, reopen); `ResolveNoteDialog` asks for the resolution note (required for a Finding); the diff gutter has one marker per kind with a count; the thread index filters by kind and state; and the conclusion card shows the outcome, the findings in the report with their notes, and the signers. At the top of the page `ReviewStatusPanel` answers "Where are we?": each reviewer with the state of the ballot (Not started, Draft, Handed in) and of the signature (Signed, Not signed, Signed, then the review changed), the checks answered differently with a Discuss button, the numbers of open questions and findings as an icon and text, one primary next-action button, and a notice instead of the disputes for a viewer who has not handed in their own ballot; a reviewer whose signature no longer matches the report can open "What changed since {name} signed", a list of the changes that can alter the report, derived by `ReviewStatusService` from the audit trail. */

        metadata info : SoftwareInfo {
            sourceFiles = ("src/DemaConsulting.ReviewCenter/Web/ReviewPage.razor", "src/DemaConsulting.ReviewCenter/Web/ReviewPage.razor.cs", "src/DemaConsulting.ReviewCenter/Web/DiffView.razor", "src/DemaConsulting.ReviewCenter/Web/DiffView.razor.cs", "src/DemaConsulting.ReviewCenter/Web/SignatureWarning.razor", "src/DemaConsulting.ReviewCenter/Web/SignatureWarning.razor.cs", "src/DemaConsulting.ReviewCenter/Web/ThreadKindBadge.razor", "src/DemaConsulting.ReviewCenter/Web/ThreadKindBadge.razor.cs", "src/DemaConsulting.ReviewCenter/Web/ThreadComposer.razor", "src/DemaConsulting.ReviewCenter/Web/ThreadComposer.razor.cs", "src/DemaConsulting.ReviewCenter/Web/ThreadCard.razor", "src/DemaConsulting.ReviewCenter/Web/ThreadCard.razor.cs", "src/DemaConsulting.ReviewCenter/Web/ResolveNoteDialog.razor", "src/DemaConsulting.ReviewCenter/Web/ResolveNoteDialog.razor.cs", "src/DemaConsulting.ReviewCenter/Web/ReviewStatusPanel.razor", "src/DemaConsulting.ReviewCenter/Web/ReviewStatusPanel.razor.cs", "src/DemaConsulting.ReviewCenter/Web/ReviewLinks.cs");
            testFiles = ("test/DemaConsulting.ReviewCenter.Tests/Web/ReviewPageTests.cs", "test/DemaConsulting.ReviewCenter.Tests/Web/ReviewPageFollowUpTests.cs", "test/DemaConsulting.ReviewCenter.Tests/Web/ReviewPageRepositoryTests.cs", "test/DemaConsulting.ReviewCenter.Tests/Web/ReviewPageDiffTests.cs", "test/DemaConsulting.ReviewCenter.Tests/Web/ReviewPageUnreadTests.cs", "test/DemaConsulting.ReviewCenter.Tests/Web/ReviewPageRejectedTests.cs", "test/DemaConsulting.ReviewCenter.Tests/Web/ReviewPageCheckThreadTests.cs", "test/DemaConsulting.ReviewCenter.Tests/Web/ReviewPageThreadKindTests.cs", "test/DemaConsulting.ReviewCenter.Tests/Web/ReviewPageConclusionCardTests.cs", "test/DemaConsulting.ReviewCenter.Tests/Web/ThreadKindBadgeTests.cs", "test/DemaConsulting.ReviewCenter.Tests/Web/ThreadComposerTests.cs", "test/DemaConsulting.ReviewCenter.Tests/Web/ThreadCardTests.cs", "test/DemaConsulting.ReviewCenter.Tests/Web/ResolveNoteDialogTests.cs", "test/DemaConsulting.ReviewCenter.Tests/Web/ReviewStatusPanelTests.cs", "test/DemaConsulting.ReviewCenter.Tests/Web/DiffViewMarkerTests.cs", "test/DemaConsulting.ReviewCenter.Tests/Web/ReviewLinksTests.cs", "test/DemaConsulting.ReviewCenter.Tests/Web/ReviewDeepLinkTests.cs", "test/DemaConsulting.ReviewCenter.Tests/Web/BallotMaskingPageTests.cs");
            designFiles = ("docs/design/review-center/web/review-page.md");
            verificationFiles = ("docs/verification/review-center/web/review-page.md");
            requirementFiles = ("docs/reqstream/review-center/web/review-page.yaml");
        }
    }
}
