package ReviewCenter {
    private import SoftwareItemMetadata::*;

    part def HelpPage {
        doc /* Built-in help: the index at /help, one page for each help topic at /help/{topic} with a shared frame and links to the previous and next topic, the list of topics that feeds them, a friendly page for an unknown help address, and the Signed attestation topic that says what the signature proves and does not prove and what the PDF lists (including who answered each check and when), the Managing project members topic that explains how an administrator of a project adds a member by the exact user name, creates an account with a temporary password, changes a role, and removes a member, and the API tokens topic that explains personal access tokens, the API, and what a token cannot do, and the Evidence settings topic that explains who may change the evidence settings of a project, the anonymous access switches and their exposure, the PDF content switches and their regulatory warning, and the Content scope section of every PDF, and the Two-factor sign-in topic that explains how to set it up, sign in and sign with a code, use the recovery codes, turn it off, and get a reset, and the Your inbox topic that explains the eight groups of the inbox, the New marker, and Mark all as read, and the E-mail notifications topic that explains in plain language what a notification mail names, what it never holds, how an address is confirmed with a mailed code, the three choices of when to get e-mail, how to stop the mail, and that it is there only when the administrator has set up mail; the topics on getting started, signing, and API tokens also mention the identity provider, and the signing topic also states the rule that the person who reopened a review cannot sign it again. */

        // Screenshots of the help topics are non-source data in src/DemaConsulting.ReviewCenter/wwwroot/help/.
        metadata info : SoftwareInfo {
            sourceFiles = ("src/DemaConsulting.ReviewCenter/Web/HelpTopicFrame.razor", "src/DemaConsulting.ReviewCenter/Web/HelpTopics.cs", "src/DemaConsulting.ReviewCenter/Web/HelpApiTokensPage.razor", "src/DemaConsulting.ReviewCenter/Web/HelpAttestationPage.razor", "src/DemaConsulting.ReviewCenter/Web/HelpAuditPage.razor", "src/DemaConsulting.ReviewCenter/Web/HelpChecklistPage.razor", "src/DemaConsulting.ReviewCenter/Web/HelpChecklistTemplatePage.razor", "src/DemaConsulting.ReviewCenter/Web/HelpCommentsPage.razor", "src/DemaConsulting.ReviewCenter/Web/HelpCreatingReviewPage.razor", "src/DemaConsulting.ReviewCenter/Web/HelpEvidenceSettingsPage.razor", "src/DemaConsulting.ReviewCenter/Web/HelpGettingStartedPage.razor", "src/DemaConsulting.ReviewCenter/Web/HelpInboxPage.razor", "src/DemaConsulting.ReviewCenter/Web/HelpMembersPage.razor", "src/DemaConsulting.ReviewCenter/Web/HelpNotFoundPage.razor", "src/DemaConsulting.ReviewCenter/Web/HelpNotificationsPage.razor", "src/DemaConsulting.ReviewCenter/Web/HelpPage.razor", "src/DemaConsulting.ReviewCenter/Web/HelpPlanningPage.razor", "src/DemaConsulting.ReviewCenter/Web/HelpReadingReviewPage.razor", "src/DemaConsulting.ReviewCenter/Web/HelpSigningPage.razor", "src/DemaConsulting.ReviewCenter/Web/HelpTwoFactorPage.razor");
            testFiles = ("test/DemaConsulting.ReviewCenter.Tests/Web/HelpPageTests.cs");
            designFiles = ("docs/design/review-center/web/help-page.md");
            verificationFiles = ("docs/verification/review-center/web/help-page.md");
            requirementFiles = ("docs/reqstream/review-center/web/help-page.yaml");
        }
    }
}
