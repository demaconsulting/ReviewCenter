package ReviewCenter {
    private import SoftwareItemMetadata::*;

    part def ProjectPage {
        doc /* Pages that show one project to a user who may see it (a hidden project looks like a project that does not exist) with its reviews as rows, each with its stage (Setup, In review, or Approved), the signed and required slots, the ballots handed in out of the reviewers (with the names of those who have not handed in, and a note that some details are hidden for a viewer who may not see the other ballots yet), who the review waits on, what blocks it, its due date with an overdue mark, and the time of its last activity, as rows of an overview that can be filtered by stage, overdue, blocked, and text, sorted by activity, due date, or progress, and paged (25 per page) with the choices kept in the address, a link to the plan page when a repository of the project is enabled, Repositories, Audit trail, and Evidence settings buttons for whoever administers the project, a Checklist button, and, for those administrators only (project admins and system administrators), a Review rules card with the switches for independent reviewers, non-author checklist answers, and non-reopener signing (the last two are enforced by Core and apply to every project; each changed rule is saved from the loaded value and audited) and a line that names the checklist that new reviews start with, the members of the project with their roles to change or remove and a button to add one; the separate pages to add an existing user by the exact user name and to create a local account for the project, which shows the generated temporary password once; the evidence settings page, where whoever administers the project switches anonymous access to the evidence index and the attestation PDFs (both off by default) and the content of the PDFs (discussion threads, reviewer names, checklist wording, file list and hashes, git context; all on by default) with regulatory and exposure warnings, saves them together with an audit entry, and refuses a stale save; the checklist template page, where whoever administers the project exports the current checklist and the built-in default as JSON, imports a definition by paste or file, sees every validation error with its path, a preview and a compact comparison with the current checklist, replaces the checklist or resets it to the built-in default after a confirmation (existing reviews keep their checklist), and is told when someone else changed it meanwhile; and the separate page with the form to create a review from uploaded files or from an enabled git repository of the project (head revision, optional baseline revision, selection), which can also create the review as a follow-up of an earlier review of the project, with a preview of what it carries over and a confirmation before open threads are dropped. A review that follows another is tagged on the list with a link to the earlier review. Every handler re-checks access through the shared guard and clears loaded data when it is gone. */

        metadata info : SoftwareInfo {
            sourceFiles = ("src/DemaConsulting.ReviewCenter/Web/ProjectPage.razor", "src/DemaConsulting.ReviewCenter/Web/ProjectPage.razor.cs", "src/DemaConsulting.ReviewCenter/Web/NewReviewPage.razor", "src/DemaConsulting.ReviewCenter/Web/NewReviewPage.razor.cs", "src/DemaConsulting.ReviewCenter/Web/NewMemberPage.razor", "src/DemaConsulting.ReviewCenter/Web/NewMemberPage.razor.cs", "src/DemaConsulting.ReviewCenter/Web/NewMemberAccountPage.razor", "src/DemaConsulting.ReviewCenter/Web/NewMemberAccountPage.razor.cs", "src/DemaConsulting.ReviewCenter/Web/EvidenceSettingsPage.razor", "src/DemaConsulting.ReviewCenter/Web/EvidenceSettingsPage.razor.cs", "src/DemaConsulting.ReviewCenter/Web/ProjectChecklistPage.razor", "src/DemaConsulting.ReviewCenter/Web/ProjectChecklistPage.razor.cs", "src/DemaConsulting.ReviewCenter/Web/ChecklistDiff.cs");
            testFiles = ("test/DemaConsulting.ReviewCenter.Tests/Web/ProjectPageTests.cs", "test/DemaConsulting.ReviewCenter.Tests/Web/ProjectPageOverviewTests.cs", "test/DemaConsulting.ReviewCenter.Tests/Web/NewReviewPageRepositoryTests.cs", "test/DemaConsulting.ReviewCenter.Tests/Web/NewReviewPageFollowUpTests.cs", "test/DemaConsulting.ReviewCenter.Tests/Web/NewMemberPageTests.cs", "test/DemaConsulting.ReviewCenter.Tests/Web/NewMemberAccountPageTests.cs", "test/DemaConsulting.ReviewCenter.Tests/Web/EvidenceSettingsPageTests.cs", "test/DemaConsulting.ReviewCenter.Tests/Web/ProjectChecklistPageTests.cs", "test/DemaConsulting.ReviewCenter.Tests/Web/ChecklistDiffTests.cs", "test/DemaConsulting.ReviewCenter.Tests/Web/BallotMaskingPageTests.cs");
            designFiles = ("docs/design/review-center/web/project-page.md");
            verificationFiles = ("docs/verification/review-center/web/project-page.md");
            requirementFiles = ("docs/reqstream/review-center/web/project-page.yaml");
        }
    }
}
