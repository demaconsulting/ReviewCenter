package ReviewCenter {
    private import SoftwareItemMetadata::*;

    part def ChecklistPage {
        doc /* Page that shows the checklist of one review: what is left to do (status line with the state of the ballot of the signed-in reviewer, progress, a next-unanswered action), the signed-in reviewer, and the sections with their progress, one open at a time. An open section offers the applies-to-this-review switch (a reason is required when it does not) and one row per check with Pass, Fail, and N/A buttons; Fail and N/A ask for a justification next to the buttons. A reviewer who holds a slot answers in the own ballot of that slot and sees it, a draft included, while a viewer without a slot sees the consolidated checklist of the submitted ballots in a review with a single slot or a concluded review (in a review with several slots that is not concluded the standing is hidden from such a viewer, except the lead, an administrator, and an Auditor); a member without a slot sees a notice and disabled controls. In a review with several slots a Submit ballot button hands in a complete draft; in a review with one slot an answer or an edit that completes the ballot hands it in at once, so the button shows there only for a complete draft that no such answer produced (carried answers only, or no checks). When the review is approved and locked a notice says so and every control that changes the checklist is disabled. While the project requires that authors do not answer the checklist of their own review (on by default), the author of the review sees a notice and the same disabled controls, and can still use the comment threads. An answer, a change of the applicability of a section, or the hand-in of a ballot that would make a current signature out of date (a draft never does) first shows a warning next to the control that names the signers and is stored only when the reviewer confirms. On a follow-up review it marks every carried answer and section state with a Carried from badge that links to the earlier review, and shows the earlier Fail of a check that is open again, read-only. In a review with several slots, a viewer who has not handed in their own ballot sees only how many ballots are handed in, never the answers of the others or a count of disputed checks; a viewer who has handed in sees the differing answers side by side under the check with a Discuss button that starts a discussion thread. A complete draft offers Submit and sign as the main action (the ballot is handed in and then signed with the password and, when there is one, the code of the second factor, or, for an account of an identity provider, handed in and followed by the confirmation at the provider; the digest that is signed is the one of the record the viewer is shown after the hand-in, and when that view shows a check the submitted ballots answer differently nothing is signed and the page says that something changed, so the viewer reads the answers and signs from the review page), and a member who holds no slot can add a new slot for themselves with Assign me as reviewer. */

        metadata info : SoftwareInfo {
            sourceFiles = ("src/DemaConsulting.ReviewCenter/Web/ChecklistPage.razor", "src/DemaConsulting.ReviewCenter/Web/ChecklistPage.razor.cs", "src/DemaConsulting.ReviewCenter/Web/SignatureWarning.razor", "src/DemaConsulting.ReviewCenter/Web/SignatureWarning.razor.cs", "src/DemaConsulting.ReviewCenter/Web/SignConfirm.razor", "src/DemaConsulting.ReviewCenter/Web/SignConfirm.razor.cs");
            testFiles = ("test/DemaConsulting.ReviewCenter.Tests/Web/ChecklistPageTests.cs", "test/DemaConsulting.ReviewCenter.Tests/Web/ChecklistPageBallotTests.cs", "test/DemaConsulting.ReviewCenter.Tests/Web/ChecklistPageFollowUpTests.cs", "test/DemaConsulting.ReviewCenter.Tests/Web/ChecklistPageSideBySideTests.cs", "test/DemaConsulting.ReviewCenter.Tests/Web/ChecklistPageSubmitAndSignTests.cs", "test/DemaConsulting.ReviewCenter.Tests/Web/ChecklistPageAssignMeTests.cs", "test/DemaConsulting.ReviewCenter.Tests/Web/BallotPageTestBase.cs", "test/DemaConsulting.ReviewCenter.Tests/Web/SignConfirmTests.cs");
            designFiles = ("docs/design/review-center/web/checklist-page.md");
            verificationFiles = ("docs/verification/review-center/web/checklist-page.md");
            requirementFiles = ("docs/reqstream/review-center/web/checklist-page.yaml");
        }
    }
}
