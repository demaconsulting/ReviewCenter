package ReviewCenter {
    private import SoftwareItemMetadata::*;

    part def ReviewStore {
        doc /* Database implementation of the Core store interface that saves and reads projects (with their evidence settings, which are changed only by an atomic compare-and-set together with its audit entry), project memberships (added, changed, and removed with an audit entry that carries the project, the last enabled project administrator protected atomically on request), reviews (with their source and change kinds), file content and baseline content, comment threads (saved only open and with their first comment, with the kind of a thread and the kind and report flag of a comment; promotion, demotion, the toggle of a comment, and the resolution with its note, each with its audit entry in the same transaction), checklist snapshots and answers, reviewer slots, and signatures, the reopenings of an approved review (with their audit entry in the same transaction) and the per-project review rules (UpdateReviewRuleAsync: independent reviewers, non-author checklist answers, and non-reopener signing, each an atomic compare-and-set with its audit entry), reads the whole record of a review (including the number of reopenings), changes the optional due date of a review only by an atomic compare-and-set together with its audit entry, changes the optional review conclusion text of a review (part of the record) in the same way and refuses it for a concluded review, keeps one ballot per reviewer slot (Draft or Submitted, with a compare-and-set hand-in, an automatic hand-in in a single-slot review, seeding from a follow-up, and the removal of the answers of a departed reviewer, each with its audit entry in the same transaction), refuses a signature of a record that changed, refuses a signature while a thread is open (re-checked inside the signing transaction), and refuses inside the transaction every change of the content, the threads, or the reviewers of a review that is concluded (ReviewLocked). */

        metadata info : SoftwareInfo {
            sourceFiles = ("src/DemaConsulting.ReviewCenter/Storage/ReviewStore.cs");
            testFiles = ("test/DemaConsulting.ReviewCenter.Tests/Storage/ReviewStoreTests.cs", "test/DemaConsulting.ReviewCenter.Tests/Storage/ReviewStoreRepositoryTests.cs", "test/DemaConsulting.ReviewCenter.Tests/Storage/ReviewStoreSigningTests.cs", "test/DemaConsulting.ReviewCenter.Tests/Storage/ReviewStoreMembershipTests.cs", "test/DemaConsulting.ReviewCenter.Tests/Storage/ProjectMembersStoreTests.cs", "test/DemaConsulting.ReviewCenter.Tests/Storage/EvidenceSettingsStoreTests.cs", "test/DemaConsulting.ReviewCenter.Tests/Storage/ProjectChecklistStoreTests.cs", "test/DemaConsulting.ReviewCenter.Tests/Storage/ReviewDueDateStoreTests.cs", "test/DemaConsulting.ReviewCenter.Tests/Storage/ReviewFollowUpStoreTests.cs", "test/DemaConsulting.ReviewCenter.Tests/Storage/ReviewStoreReviewConclusionTextTests.cs", "test/DemaConsulting.ReviewCenter.Tests/Storage/ReviewStoreBallotTests.cs", "test/DemaConsulting.ReviewCenter.Tests/Storage/ReviewStoreRecordContentTests.cs", "test/DemaConsulting.ReviewCenter.Tests/Storage/ReviewStoreCheckThreadTests.cs");
            designFiles = ("docs/design/review-center/storage/review-store.md");
            verificationFiles = ("docs/verification/review-center/storage/review-store.md");
            requirementFiles = ("docs/reqstream/review-center/storage/review-store.yaml");
        }
    }
}
