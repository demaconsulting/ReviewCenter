package ReviewCenter {
    private import SoftwareItemMetadata::*;

    part def ReviewCenterDbContext {
        doc /* Entity Framework Core model that maps users (with the external issuer and subject columns and a unique index over the pair), projects (with the seven boolean columns of their evidence settings and the three boolean columns of the review rules: independent reviewers, non-author checklist answers, and non-reopener signing, all on by default), project memberships, reviews, review files, threads (with their kind), comments (with their kind and the report flag), and checklist snapshots, section states, and answers, reviewer slots and signatures, the reopenings of reviews (a table that belongs to the review), git repositories, and personal access tokens (with the creator of a review) and the enrollments of the second factor with their recovery codes (a table each, with a unique index over the user and the hash of a code), the e-mail address for notifications (a row for each user, removed with the user, with the notification mode and the dispatch state) and the log of the notification mails that were sent (indexed for the counts of the limits) and the items already mailed (a row for each user, review, and kind, unique together, removed with the user or the review), the read state of the inbox (a row for each user and review, removed with either), and the indexes on the reviewer slots and the creator of a review that the inbox uses, and the optional review conclusion text of a review (at most 4000 characters), to database tables, keys, and relationships. */

        metadata info : SoftwareInfo {
            sourceFiles = ("src/DemaConsulting.ReviewCenter/Storage/ReviewCenterDbContext.cs");
            testFiles = ("test/DemaConsulting.ReviewCenter.Tests/Storage/ReviewStoreTests.cs", "test/DemaConsulting.ReviewCenter.Tests/Storage/ReviewStoreRepositoryTests.cs", "test/DemaConsulting.ReviewCenter.Tests/Storage/ReviewStoreMembershipTests.cs", "test/DemaConsulting.ReviewCenter.Tests/Storage/EvidenceSettingsStoreTests.cs", "test/DemaConsulting.ReviewCenter.Tests/Storage/ProjectChecklistStoreTests.cs", "test/DemaConsulting.ReviewCenter.Tests/Storage/ReviewDueDateStoreTests.cs", "test/DemaConsulting.ReviewCenter.Tests/Storage/ReviewFollowUpStoreTests.cs", "test/DemaConsulting.ReviewCenter.Tests/Storage/ReviewStoreRecordContentTests.cs", "test/DemaConsulting.ReviewCenter.Tests/Storage/ReviewStoreReviewConclusionTextTests.cs", "test/DemaConsulting.ReviewCenter.Tests/Storage/ReviewStoreBallotTests.cs", "test/DemaConsulting.ReviewCenter.Tests/Storage/ReviewStoreCheckThreadTests.cs", "test/DemaConsulting.ReviewCenter.Tests/Storage/RepositoryStoreTests.cs", "test/DemaConsulting.ReviewCenter.Tests/Storage/NotificationStoreModeTests.cs", "test/DemaConsulting.ReviewCenter.Tests/Storage/DatabaseSetupTests.cs");
            designFiles = ("docs/design/review-center/storage/review-center-db-context.md");
            verificationFiles = ("docs/verification/review-center/storage/review-center-db-context.md");
            requirementFiles = ("docs/reqstream/review-center/storage/review-center-db-context.yaml");
        }
    }
}
