package ReviewCenter {
    private import SoftwareItemMetadata::*;

    part def StorageSubsystem {
        doc /* Persistence of users (with the system administrator flag and, for an account of an OpenID Connect provider, its issuer and subject, unique together), projects, project memberships, reviews, review comment threads, and review checklists, reviewer slots, signatures, the git repositories of the projects, personal access tokens (by hash only), the second factor of users (the encrypted secret and the hashes of the recovery codes), the read state of the inbox of users for reviews, the notification e-mail address of users with the hash of its pending confirmation code, their notification mode, the items already mailed with the dispatch state, and the log of mails that the sending limits count, and the hash-chained audit trail in a relational database through Entity Framework Core, with SQLite as the supported provider. */

        metadata info : SoftwareInfo {
            testFiles = ("test/DemaConsulting.ReviewCenter.Tests/Storage/StorageSubsystemTests.cs");
            designFiles = ("docs/design/review-center/storage.md");
            verificationFiles = ("docs/verification/review-center/storage.md");
            requirementFiles = ("docs/reqstream/review-center/storage.yaml");
        }

        part dbContext : ReviewCenterDbContext;
        part reviewStore : ReviewStore;
        part userStore : UserStore;
        part auditStore : AuditStore;
        part repositoryStore : RepositoryStore;
        part personalAccessTokenStore : PersonalAccessTokenStore;
        part totpStore : TotpStore;
        part inboxStore : InboxStore;
        part notificationStore : NotificationStore;
        part databaseSetup : DatabaseSetup;
    }
}
