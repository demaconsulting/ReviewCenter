package ReviewCenter {
    private import SoftwareItemMetadata::*;

    part def ApiEndpoints {
        doc /* The routes of the JSON API under /api, the immutable request and answer types, and the mapping of a broken domain rule (among them the last project admin, too many attempts, a pending password change, and a review that is locked or not locked, which are conflicts with status 409) or an unusable key to an HTTP status with one problem description (application/problem+json): lists the projects the actor may see and their reviews (each with its approved flag, the number of slots required, signed, and out of date, the overdue flag, and the time of its last activity; every route of a project asks the project service first and answers a non-member like a missing project with 404), reads a review (the standing of the reviewers is masked for the token like on the pages, so a token that has not handed in a ballot in a review with several slots that is not concluded sees no failed count, dispute, or check thread; the thread kind is only counted; the outcome and the conclusion text only once the review is concluded), creates a draft review from files or from the changes of a repository, downloads the signed attestation of a concluded review, and returns the evidence index of a project (the complete reviews that have a review-set identifier, each with an absolute attestation address; never cached), and returns the checklist template of a project (the definition, version label, default flag, hash, and counts; read-only). The attestation and evidence index routes sit in a second route group with their own policies and a per-address limit (429 with Retry-After) for requests without credentials, and are the only routes a project can open to a caller without a token; every other route requires the token policy. Offers no route that signs, arranges reviewers, or reopens a review, and answers an unknown address under /api with a JSON 404. Also holds, outside the token API and the OpenAPI document, the two cookie-authenticated streaming routes of the audit export (GET /projects/{id}/audit/export for project administrators and system administrators through the audit-read access, with 404 for a project that cannot be seen and 403 for one that can be seen but not read; GET /audit/export for system administrators only; a request without a session is redirected to sign-in), which answer CSV or JSON with the chain status in the headers X-ReviewCenter-Audit-Chain and X-ReviewCenter-Audit-Chain-Broken-At, no-store caching, and an attachment file name. */

        metadata info : SoftwareInfo {
            sourceFiles = ("src/DemaConsulting.ReviewCenter/Api/ApiEndpoints.cs", "src/DemaConsulting.ReviewCenter/Api/ApiModels.cs", "src/DemaConsulting.ReviewCenter/Api/ApiProblems.cs", "src/DemaConsulting.ReviewCenter/Api/AuditExportEndpoints.cs");
            testFiles = ("test/DemaConsulting.ReviewCenter.Tests/Api/ApiEndpointsTests.cs", "test/DemaConsulting.ReviewCenter.Tests/Api/ApiEndpointsMaskingTests.cs", "test/DemaConsulting.ReviewCenter.Tests/Api/ApiProjectAccessTests.cs", "test/DemaConsulting.ReviewCenter.Tests/Api/AuditExportEndpointsTests.cs");
            designFiles = ("docs/design/review-center/api/api-endpoints.md");
            verificationFiles = ("docs/verification/review-center/api/api-endpoints.md");
            requirementFiles = ("docs/reqstream/review-center/api/api-endpoints.yaml");
        }
    }
}
