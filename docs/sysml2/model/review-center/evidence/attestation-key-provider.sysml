package ReviewCenter {
    private import SoftwareItemMetadata::*;

    part def AttestationKeyProvider {
        doc /* Chooses and loads the signing key of the attestation from the Attestation settings: a self-signed key that the server creates and keeps in a folder, protected at rest with the Data Protection key ring (a plaintext file of an earlier version is ignored with a warning, an expired key is archived and replaced, and a provider told not to create anything only describes), or a certificate of a certificate store found by its thumbprint, or a certificate with its private key in a PFX or PEM file (the password comes from a setting or a password file, the key stays in memory, and a key without a password is a warning or, with RequireEncryptedKeys, an error); describes the key and its status for the pages; applies the RequireTrustedKey policy; warns when a certificate of the store or file provider ends within ExpiryWarningDays or has ended; and warns, without refusing it for that reason, about a code-signing-only certificate that Adobe Acrobat will not trust for documents (the classification is part of the key description; chain and revocation are not checked by the server). The private key is never exported. */

        metadata info : SoftwareInfo {
            sourceFiles = ("src/DemaConsulting.ReviewCenter/Evidence/AttestationKeyProviderFactory.cs", "src/DemaConsulting.ReviewCenter/Evidence/SelfSignedKeyProvider.cs", "src/DemaConsulting.ReviewCenter/Evidence/CertificateStoreKeyProvider.cs", "src/DemaConsulting.ReviewCenter/Evidence/FileKeyProvider.cs", "src/DemaConsulting.ReviewCenter/Evidence/AttestationKeyProviderBase.cs", "src/DemaConsulting.ReviewCenter/Evidence/AttestationKeyPolicy.cs", "src/DemaConsulting.ReviewCenter/Evidence/IAttestationKeyProvider.cs", "src/DemaConsulting.ReviewCenter/Evidence/AttestationSigningKey.cs", "src/DemaConsulting.ReviewCenter/Evidence/AttestationKeyInfo.cs", "src/DemaConsulting.ReviewCenter/Evidence/AttestationKeyException.cs", "src/DemaConsulting.ReviewCenter/Evidence/AttestationOptions.cs");
            testFiles = ("test/DemaConsulting.ReviewCenter.Tests/Evidence/AttestationKeyPolicyTests.cs", "test/DemaConsulting.ReviewCenter.Tests/Evidence/SelfSignedKeyProviderTests.cs", "test/DemaConsulting.ReviewCenter.Tests/Evidence/CertificateStoreKeyProviderTests.cs", "test/DemaConsulting.ReviewCenter.Tests/Evidence/FileKeyProviderTests.cs");
            designFiles = ("docs/design/review-center/evidence/attestation-key-provider.md");
            verificationFiles = ("docs/verification/review-center/evidence/attestation-key-provider.md");
            requirementFiles = ("docs/reqstream/review-center/evidence/attestation-key-provider.yaml");
        }
    }
}
