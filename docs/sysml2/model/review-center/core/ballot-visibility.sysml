package ReviewCenter {
    private import SoftwareItemMetadata::*;

    part def BallotVisibility {
        doc /* Decides whether a viewer may see what the other reviewers of a review with several reviewer slots answered (only after the viewer has handed in their own ballot, or when the viewer leads the review, administers the project, is a system administrator or an auditor, or the review is concluded), and keeps the answers, the disputed and failed counts, the provisional outcome, the conclusion text, the discussions about checks, and the audit details of answers from a viewer who may not, an API token included (a token is never the lead, an administrator, or an auditor; the API reads the standing with a viewer through `GetConsolidatedAsync` and has no unmasked read). Gives the checklist page its ballot view (the differing answers side by side, the counts of handed-in ballots, and the Assign me and Submit and sign offers) and tells which discussions a viewer may start. Masking is applied when the data is read; the stored record, the audit chain, and the signature checks are untouched. */

        metadata info : SoftwareInfo {
            sourceFiles = ("src/DemaConsulting.ReviewCenter.Core/BallotVisibility.cs", "src/DemaConsulting.ReviewCenter.Core/BallotView.cs", "src/DemaConsulting.ReviewCenter.Core/ThreadCapabilities.cs", "src/DemaConsulting.ReviewCenter.Core/AuditMasking.cs");
            testFiles = ("test/DemaConsulting.ReviewCenter.Tests/Core/BallotVisibilityTests.cs", "test/DemaConsulting.ReviewCenter.Tests/Core/AuditMaskingTests.cs", "test/DemaConsulting.ReviewCenter.Tests/Core/BallotMaskingServiceTests.cs");
            designFiles = ("docs/design/review-center/core/ballot-visibility.md");
            verificationFiles = ("docs/verification/review-center/core/ballot-visibility.md");
            requirementFiles = ("docs/reqstream/review-center/core/ballot-visibility.yaml");
        }
    }
}
