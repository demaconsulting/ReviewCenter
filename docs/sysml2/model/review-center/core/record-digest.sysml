package ReviewCenter {
    private import SoftwareItemMetadata::*;

    part def RecordDigest {
        doc /* Calculates the digest of a review record: the SHA-256 of a canonical text of the fingerprint, the source (upload, or repository, commits, selection), every change (path, kind, baseline and head hashes), the checklist answers, the sections that do not apply, the review conclusion text (only when there is one, so a record without one keeps its digest), and a `report` block (version 2) that lists the Findings and the included comments of every thread with their kind, side, anchor, author, text, and inclusion flag (a thread about a check is anchored by the check identifier, `thread check {id}`, instead of a file and lines), but not whether a thread is open or resolved, so chat and the state of a thread are not part of the digest, and, only when the review was reopened, the number of reopenings (so a digest of a review that was never reopened is unchanged). A signature binds itself to this digest. Also calculates, separately and without storing it, the fingerprint of the submitted ballots of the slots (the answers, justifications, answerers, times and section states, with the slots numbered by ordinal and no display name), which the attestation prints in its Ballots appendix. */

        metadata info : SoftwareInfo {
            sourceFiles = ("src/DemaConsulting.ReviewCenter.Core/RecordDigest.cs", "src/DemaConsulting.ReviewCenter.Core/ReviewRecord.cs");
            testFiles = ("test/DemaConsulting.ReviewCenter.Tests/Core/RecordDigestTests.cs", "test/DemaConsulting.ReviewCenter.Tests/Core/RecordDigestFollowUpTests.cs", "test/DemaConsulting.ReviewCenter.Tests/Core/RecordDigestReportTests.cs", "test/DemaConsulting.ReviewCenter.Tests/Core/RecordDigestCheckThreadTests.cs", "test/DemaConsulting.ReviewCenter.Tests/Core/RecordDigestBallotFingerprintTests.cs");
            designFiles = ("docs/design/review-center/core/record-digest.md");
            verificationFiles = ("docs/verification/review-center/core/record-digest.md");
            requirementFiles = ("docs/reqstream/review-center/core/record-digest.yaml");
        }
    }
}
