package ReviewCenter {
    private import SoftwareItemMetadata::*;

    part def ThreadService {
        doc /* Starts comment threads on a file of a review or on a check of its frozen checklist, appends replies, resolves and reopens threads, enforces the comment rules (a comment on the lines of a file only when they exist on the chosen side: the head, or the baseline for a file that has one; a thread carries its side), records the signed-in user as the author, and reads threads back. A thread is a Question (chat, the default) or a Finding (`ThreadKind`); every comment is a Comment or a Resolution (`ReviewCommentKind`) and carries `IncludeInReport` (default false). Only the included comments of the thread are part of the record digest, so chat never makes a signature out of date. The service promotes a Question to a Finding and demotes it back (`PromoteAsync`, `DemoteAsync`), toggles the inclusion of a comment (`SetCommentReportAsync`), and resolves a thread (a Finding needs a resolution note, which is stored as a Resolution comment in the same transaction; the store compares the kind it reads in that transaction with the kind the service saw and refuses a changed kind with the RecordChanged rule, and a resolved thread can only be reached through that resolve, since the only other state change is a reopen); the permissions come from the pure helper `ThreadKindRules` and the role names from `ReviewActorRoles`, an Auditor can never promote or demote, and every such change is audited. Every change by an actor requires that the actor may see the project (`IProjectAccess`) and that the review is not concluded (ReviewLocked, `ReviewLock.IsConcluded`), and refuses a change that would alter the digest and so make a current signature out of date unless the caller acknowledges the affected slots (SignaturesWouldBecomeOutOfDate). Also derives what a reader needs to navigate the discussion: a thread's last activity, the thread index (rows across all files, filtered by state and ordered by activity), and the one-sentence next step, which also names the unanswered checklist checks and the checks answered Fail. It also tells a viewer which actions are allowed (`GetCapabilitiesAsync`: per thread whether it may be promoted, demoted or resolved and which replies may be added to or removed from the report, by the same rules that the actions enforce; nothing for an Auditor, an API token or a concluded review), and `ThreadCounts` counts the threads by kind and state for the summary strip, the progress and the inbox. */

        metadata info : SoftwareInfo {
            sourceFiles = ("src/DemaConsulting.ReviewCenter.Core/ThreadService.cs", "src/DemaConsulting.ReviewCenter.Core/ThreadCounts.cs", "src/DemaConsulting.ReviewCenter.Core/ThreadCapabilities.cs", "src/DemaConsulting.ReviewCenter.Core/ThreadKindRules.cs", "src/DemaConsulting.ReviewCenter.Core/ThreadKind.cs", "src/DemaConsulting.ReviewCenter.Core/ReviewCommentKind.cs", "src/DemaConsulting.ReviewCenter.Core/ReviewActorRoles.cs", "src/DemaConsulting.ReviewCenter.Core/ReviewThread.cs", "src/DemaConsulting.ReviewCenter.Core/ThreadAnchor.cs", "src/DemaConsulting.ReviewCenter.Core/CheckThreadRules.cs", "src/DemaConsulting.ReviewCenter.Core/ReviewComment.cs", "src/DemaConsulting.ReviewCenter.Core/ReviewThreadState.cs", "src/DemaConsulting.ReviewCenter.Core/FileText.cs");
            testFiles = ("test/DemaConsulting.ReviewCenter.Tests/Core/ThreadServiceTests.cs", "test/DemaConsulting.ReviewCenter.Tests/Core/ThreadServiceReportTests.cs", "test/DemaConsulting.ReviewCenter.Tests/Core/ThreadCapabilitiesTests.cs", "test/DemaConsulting.ReviewCenter.Tests/Core/ThreadKindRulesTests.cs", "test/DemaConsulting.ReviewCenter.Tests/Core/CheckThreadTests.cs", "test/DemaConsulting.ReviewCenter.Tests/Core/CheckThreadRulesTests.cs");
            designFiles = ("docs/design/review-center/core/thread-service.md");
            verificationFiles = ("docs/verification/review-center/core/thread-service.md");
            requirementFiles = ("docs/reqstream/review-center/core/thread-service.yaml");
        }
    }
}
