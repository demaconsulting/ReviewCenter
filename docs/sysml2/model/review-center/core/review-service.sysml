package ReviewCenter {
    private import SoftwareItemMetadata::*;

    part def ReviewService {
        doc /* Creates draft reviews from uploaded files or from the changes between two revisions of a registered git repository, freezing the changed content, enforcing the review and upload rules, and reads reviews back. Requires that the actor may see the project (`IProjectAccess`) before creating a review, and takes the repository only from the same project. Records the creator of a review and whether an actor that came through a personal access token created it, naming the token id in the audit entry. Also reads one file back as a line diff between its baseline and head content (`GetDiffAsync`), computed by `LineDiff`. Holds the optional due date of a review (a UTC calendar day, not part of the record digest): checks it at creation, tells whether a review is overdue (`IsOverdue`), and lets a project or system administrator or the creator, but never an actor of a token, change or clear it on a review that is not approved (`SetDueDateAsync`, audited as `review.due-date-changed`). Also creates a follow-up review of an earlier review of the same project (`followsReviewId`): checks that it fits and carries over what the submitted ballots of the earlier review agree on (the agreed Pass and not-applicable answers and the not-applicable sections, never a draft, a disputed or pending check, or a Fail; they become baseline rows that seed the draft ballot of every slot), and the open threads with their kind and the report flag of every comment (`FollowUpCarry`), all in the same save as the review. Tells, without writing anything, what such a follow-up would carry for a set of files (`PreviewFollowUpAsync`, a result of type `FollowUpPreview`, which also counts the threads about a check that a follow-up leaves out, `CheckThreadsLeftOut`). Never carries the review conclusion text to a follow-up. */

        metadata info : SoftwareInfo {
            sourceFiles = ("src/DemaConsulting.ReviewCenter.Core/ReviewService.cs", "src/DemaConsulting.ReviewCenter.Core/FollowUpCarry.cs", "src/DemaConsulting.ReviewCenter.Core/FollowUpPreview.cs", "src/DemaConsulting.ReviewCenter.Core/ReviewCarryOver.cs", "src/DemaConsulting.ReviewCenter.Core/Review.cs", "src/DemaConsulting.ReviewCenter.Core/ReviewFile.cs", "src/DemaConsulting.ReviewCenter.Core/ReviewState.cs", "src/DemaConsulting.ReviewCenter.Core/RepositoryReviewResult.cs", "src/DemaConsulting.ReviewCenter.Core/UploadedFile.cs");
            testFiles = ("test/DemaConsulting.ReviewCenter.Tests/Core/ReviewServiceTests.cs", "test/DemaConsulting.ReviewCenter.Tests/Core/ReviewServiceRepositoryTests.cs", "test/DemaConsulting.ReviewCenter.Tests/Core/ReviewServiceChecklistTests.cs", "test/DemaConsulting.ReviewCenter.Tests/Core/ReviewServiceDueDateTests.cs", "test/DemaConsulting.ReviewCenter.Tests/Core/ReviewServiceFollowUpTests.cs", "test/DemaConsulting.ReviewCenter.Tests/Core/FollowUpCarryTests.cs");
            designFiles = ("docs/design/review-center/core/review-service.md");
            verificationFiles = ("docs/verification/review-center/core/review-service.md");
            requirementFiles = ("docs/reqstream/review-center/core/review-service.yaml");
        }
    }
}
