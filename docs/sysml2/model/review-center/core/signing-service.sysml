package ReviewCenter {
    private import SoftwareItemMetadata::*;

    part def SigningService {
        doc /* Adds, changes, and removes the reviewer slots of a review (only for a member or system administrator who can see the project; refused for an actor that came through a personal access token), records a signature after the signer, who must be a member of the project, has entered the password again (a failed re-authentication is audited; an actor that came through a token can never sign; a user of an OpenID Connect provider instead needs a live single-use proof of a new sign-in at the provider, spent when the signature is saved, and a missing proof is refused and audited; a signer with a second factor must also give a fresh code of the authenticator app, which is never a recovery code), and computes the approval status of a review from the record and its signatures, marking a slot assignee who is no longer a project member or whose account is disabled (`SlotMember.Enabled`), and carrying the counts behind the blockers (open threads, unanswered checks, failed checks, disputed checks) as numbers next to the blocker sentences, and the number of reviewer slots that have not handed in their ballot as a plain count with no blocker sentence of its own (other slots' drafts do not block signing; they only keep the review from concluding), and the state of the ballot of each slot (`SlotStatus.Ballot`, progress that a masked status keeps), and, for an out-of-date slot, the display name of the person who gave its newest signature (`SlotStatus.LapsedSignerName`, the alternate when the alternate signed; a masked status keeps it). Offers the enabled members of a project as slot candidates, and assigns slots only to members. A signature needs that the own ballot of the signer is submitted (BallotNotSubmitted) and that nothing blocks the review: the checks are read from the consolidated checklist of the submitted ballots, a check that is pending or disputed between the ballots blocks signing, an agreed Fail does not block (it makes the agreed outcome Rejected), and the ballots of the other slots need not be submitted (early signing). A signature records the agreed outcome (`ReviewSignature.Outcome`: Approved, or Rejected when the ballots agree on a Fail); a Rejected outcome without a conclusion text is refused with `ConclusionRequired` (or with `SigningNotAllowed` when other blockers exist). A review is concluded and locked (approved or rejected) only when it is concluded (`IsConcluded`): every slot has signed for the current record with the agreed outcome, every ballot is submitted, nothing is pending or disputed, no thread is open, and a Rejected outcome has a conclusion text; signing every slot is not enough by itself. Adding, changing, and removing a slot and signing are then refused with the ReviewLocked rule (the shared helper `ReviewLock` holds the one definition: `IsConcluded` is true when there is at least one slot, every slot has submitted its ballot and is signed for the current record with the agreed outcome, no thread is open, no check is pending or disputed, and a Rejected outcome has a conclusion text; `ConcludedOutcome` names the outcome; adding, changing, and removing slots and signing are refused with `ReviewLocked` once the review is concluded; an open thread, chat or included, also blocks signing with `SigningNotAllowed`, a rule separate from the digest comparison), and only an administrator of the project or a system administrator, never an actor that came through a token, can reopen it with a reason of one to 250 characters (`ReopenReviewAsync`, an audited `review.reopened` entry, the reopening kept as a `ReviewReopen`, listed with the approval); the earlier signatures then stay as history, out of date, and every slot must sign again. While the project requires independent reviewers, the user who created the review can neither be put in a slot nor sign it. While the project requires that the person who reopened a review does not sign it again (on by default, for every project), that user cannot sign a slot of the review (`ReopenerCannotSign`), and a reopen is refused when a slot would be left without anyone who may sign (`ReopenWouldStrandSlot`; the pure helper `ReopenRules` computes the stranded slots). With the helper `SignatureImpact`, it also computes which current signatures a change of the consolidated checklist (an answer or a hand-in that changes the agreed standing; a change that leaves it as it is, and a draft, make none out of date), of the slots (a reviewer who leaves a slot takes back the answers of the ballot), or of the report content of a thread (an included comment, a promotion, a demotion, a resolution note) would make out of date, and the callers refuse the change with the SignaturesWouldBecomeOutOfDate rule, naming each affected slot number and signer, unless the caller acknowledges the slots. Also defines the slot, signature, role, approval, reopen, and status types of the Core subsystem. */

        metadata info : SoftwareInfo {
            sourceFiles = ("src/DemaConsulting.ReviewCenter.Core/SigningService.cs", "src/DemaConsulting.ReviewCenter.Core/ReviewLock.cs", "src/DemaConsulting.ReviewCenter.Core/SignatureImpact.cs", "src/DemaConsulting.ReviewCenter.Core/ReopenRules.cs", "src/DemaConsulting.ReviewCenter.Core/ReviewReopen.cs", "src/DemaConsulting.ReviewCenter.Core/ReviewerSlot.cs", "src/DemaConsulting.ReviewCenter.Core/ReviewSignature.cs", "src/DemaConsulting.ReviewCenter.Core/SlotRole.cs", "src/DemaConsulting.ReviewCenter.Core/ReviewApproval.cs");
            testFiles = ("test/DemaConsulting.ReviewCenter.Tests/Core/SigningServiceTests.cs", "test/DemaConsulting.ReviewCenter.Tests/Core/SigningServiceExternalTests.cs", "test/DemaConsulting.ReviewCenter.Tests/Core/SigningServiceTotpTests.cs", "test/DemaConsulting.ReviewCenter.Tests/Core/ReopenRulesTests.cs", "test/DemaConsulting.ReviewCenter.Tests/Core/SigningServiceOpenThreadTests.cs", "test/DemaConsulting.ReviewCenter.Tests/Core/ThreadServiceTests.cs", "test/DemaConsulting.ReviewCenter.Tests/Core/AuditEventTests.cs", "test/DemaConsulting.ReviewCenter.Tests/Core/CountingUserStore.cs", "test/DemaConsulting.ReviewCenter.Tests/Core/ChecklistServiceTests.cs", "test/DemaConsulting.ReviewCenter.Tests/Core/SignatureTestExtensions.cs");
            designFiles = ("docs/design/review-center/core/signing-service.md");
            verificationFiles = ("docs/verification/review-center/core/signing-service.md");
            requirementFiles = ("docs/reqstream/review-center/core/signing-service.yaml");
        }
    }
}
