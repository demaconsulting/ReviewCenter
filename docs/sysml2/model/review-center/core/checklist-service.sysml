package ReviewCenter {
    private import SoftwareItemMetadata::*;

    part def ChecklistService {
        doc /* Provides the review checklist: the default checklist (sections of checks, taken from the Continuous Compliance review template), the frozen copy a review keeps from its creation, and the answers. Marks sections as applicable or not (a reason is required when not), records Pass, Fail, or N/A for each check (a justification is required for Fail and N/A) with the signed-in user (user name and display name) and the UTC time in the ballot of the reviewer slot of that user (the answers and the section states are kept per slot; an actor without a slot, an administrator included, is refused with NoReviewerSlot), hands in the ballot of a slot (`SubmitBallotAsync`: an incomplete ballot is refused with BallotIncomplete, the hand-in is idempotent, every later edit makes the ballot a draft again, and in a review with a single slot the answer that completes the ballot hands it in), keeps a draft visible to its owner only while a viewer without a slot reads the consolidated checklist of the submitted ballots in a review with a single slot or a concluded review (in a review with several slots that is not concluded such a viewer gets a masked state with no standing, unless the viewer is the lead, an administrator, or an Auditor; a read without a viewer is for tests and internal reads only, and the API reads the consolidated standing with `GetConsolidatedAsync`, which requires a viewer and gives an API token the masked state because a token is never the lead, an administrator, or an Auditor), requires that the actor may see the project (`IProjectAccess`) and that the review is not approved and locked (ReviewLocked), refuses a change that would make a current signature out of date unless the caller acknowledges the affected slots (SignaturesWouldBecomeOutOfDate), refuses the author of the review to answer a check or change the applicability of a section while the project requires that authors do not answer the checklist of their own review (AuthorCannotAnswer; on by default, for every project; reads are not affected, and `ChecklistState.AuthorBlocked` tells the page), enforces these rules, and derives the progress per section and overall (of the consolidated checklist, or of the own ballot for its slot owner), completeness, and the first unanswered check, and audits the answers, the applicability changes, and the ballot actions (ballot.submitted, ballot.reopened, ballot.reassigned). Also holds the review conclusion text of a review (a free text of at most 4000 characters, not the approved or rejected conclusion): a primary or alternate reviewer of any slot or the lead may set, change, or clear it while the review is not concluded (ReviewLocked), the change is part of the record digest and needs the acknowledgment of the affected reviewers like any other change of the record, an update that lost a race is refused (RecordChanged), and the audit entry `review.conclusion-changed` carries lengths only, never the text. */

        metadata info : SoftwareInfo {
            sourceFiles = ("src/DemaConsulting.ReviewCenter.Core/ChecklistService.cs", "src/DemaConsulting.ReviewCenter.Core/ChecklistState.cs", "src/DemaConsulting.ReviewCenter.Core/ChecklistDefinition.cs", "src/DemaConsulting.ReviewCenter.Core/ChecklistValidator.cs", "src/DemaConsulting.ReviewCenter.Core/ChecklistValidationResult.cs", "src/DemaConsulting.ReviewCenter.Core/DefaultChecklist.cs", "src/DemaConsulting.ReviewCenter.Core/ReviewChecklist.cs", "src/DemaConsulting.ReviewCenter.Core/ChecklistAnswer.cs", "src/DemaConsulting.ReviewCenter.Core/ChecklistSectionState.cs", "src/DemaConsulting.ReviewCenter.Core/ChecklistBallot.cs", "src/DemaConsulting.ReviewCenter.Core/ChecklistProgress.cs", "src/DemaConsulting.ReviewCenter.Core/ChecklistOutcome.cs");
            testFiles = ("test/DemaConsulting.ReviewCenter.Tests/Core/ChecklistServiceTests.cs", "test/DemaConsulting.ReviewCenter.Tests/Core/ChecklistServiceReviewConclusionTextTests.cs", "test/DemaConsulting.ReviewCenter.Tests/Core/ChecklistValidatorTests.cs");
            designFiles = ("docs/design/review-center/core/checklist-service.md");
            verificationFiles = ("docs/verification/review-center/core/checklist-service.md");
            requirementFiles = ("docs/reqstream/review-center/core/checklist-service.yaml");
        }
    }
}
